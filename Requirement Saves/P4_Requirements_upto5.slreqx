# P4_Requirements_upto5

## #1: Safety on Design (Functional)

### #109: Safety on Design (General) (Functional)

#### #168: ISO 26262 (Functional)
The system should adhere to ISO 26262 standard.

#### #169: IEC 60034 (Functional)
The System Should Adhere to IEC 60034 Rotating Electrical Machines Standard

#### #170: ISO 16750 (Functional)
The System should adhere to ISO 16750 Vehicle Enviromental testing Standard

#### #171: IEC 60068 (Functional)
The system should adhere to IEC 60068 Environmental Testing standard.

#### #172: ISO 20653 (Functional)
The system should adhere to ISO 20653 IP classification standard.
Assumption is IP6K9K

#### #173: ISO 6336 (Functional)
The system should adhere to ISO 6336 Load Calculations for Helical Gears standard

#### #174: SAE J2555_201709 (Functional)
The system shall comply/be evaluated against SAE Standard: Vehicle Idle Gear Rattle Evaluation Procedure(STABILIZED Sep 2017) J2555_201709

#### #175: SAE J2606_201709 (Functional)
The system shall comply/be evaluated against the SAE Standard: Drain and Fill Plug for use on Engines, Transmissions, and Axles(STABILIZED Sep 2017) J2606_201709

#### #176: SAE J2908_201709 (Functional)
The system shall comply/be evaluated against the SAE Standard : Vehicle Power Test for Electrified Powertrains J2908_201709

#### #177: SAE J306_201708 (Functional)
The system shall comply/be evaluated against the SAE Standard: Automotive Gear Lubricant Viscosity Classification J306_201708

#### #178: SAE J1085_201702 (Functional)
The system shall comply/be evaluated against the SAE Standard: Testing Dynamic Properties of Elastomeric Isolators (STABILIZED Feb 2017) J1085_201702

#### #179: SAE J2455_201504 (Functional)
The system shall comply/be evaluated against the SAE Standard: Drivetrain Systems Vibration Analysis Data Requirements(STABILIZED Apr 2015) J2455_201504

#### #180: SAE J308_200703 (Functional)
The system shall comply/be evaluated against the SAE Standard: Axle and Manual Transmission Lubricants J308_200703

#### #181: SAE J649_201803 (Functional)
The system shall comply/be evaluated against the SAE Standard: Automatic Transmission Functions—Terminology J649_201803

#### #182: SAE J2907_201802 (Functional)
The system shall comply/be evaluated against the SAE Standard: Performance Characterization of Electrified Powertrain Motor-Drive Subsystem J2907_201802

#### #183: SAE J915_201703 (Functional)
The system shall comply/be evaluated against the SAE Standard: Automatic Transmissions - Manual Control Sequence(STABILIZED Mar 2017) J915_201703

#### #184: SAE Standard: Regulation No 85 of the Economic Commission for Europe of the United Nations (Functional)
Uniform provisions concerning the approval of internal combustion engines or electric drive trains intended for the propulsion of motor vehicles of categories M and N with regard to the measurement of net power and the maximum 30

#### #185: IEC 60349-2 (2010) (Functional)
The system shall comply/be evaluated against Standard: IEC 60349-2 (2010) - Electric traction - Rotating electrical machines for rail and road vehicles - Part 2: Electronic converter-fed alternating current motors

#### #186: Standard: IEEE 522 (Functional)
The system shall comply/be evaluated against Standard: IEEE 522 - Guide for Testing Turn Insulation of Form-Wound Stator Coils for AC Electric Machines

#### #187: IEEE 95-2002 (Functional)
The system shall comply/be evaluated against Standard: IEEE 95-2002 – Recommended Practice for Insulation Testing of AC Electric Machinery with High Direct Voltage

#### #188: ISO 9614-2 (Functional)
The system shall comply/be evaluated against the Standard: ISO 9614-2 Determination of sound power levels of noise sources using sound intensity – Measurement by scanning

#### #189: ISO 374X (Functional)
The system shall comply/be evaluated against the Standard: ISO 374X series – Determination of sound power levels and sound energy levels of noise sources using sound pressure

#### #190: IEC 61934 (Functional)
The system shall comply/be evaluated against the Standard: IEC 61934 – Electrical insulating materials and systems – Electrical measurement of partial discharges under short rise time and repetitive voltage impulses

#### #191: IEC 60034-1 (Functional)
The system shall comply/be evaluated against the Standard: IEC 60034-1 – Rotating electrical machines – Rating and performance

#### #192: IEC 60034-2-1 (Functional)
The system shall comply/be evaluated against the Standard: IEC 60034-2-1 Rotating electrical machines – Standard methods for determining losses and efficiency from tests

#### #193: IEC 60034-4 (Functional)
The system shall comply/be evaluated against the Standard: IEC 60034-4 Rotating electrical machines – Methods for determining synchronous machines quantities from tests

#### #194: IEC 60034-18-41 (Functional)
The system shall comply/be evaluated against the Standard: IEC 60034-18-41 Partial discharge free electrical insulation systems (Type I) used in rotating electrical machines fed from voltage converters – Qualification and quality control tests

#### #195: IEC 60034-9 (Functional)
The system shall comply/be evaluated against the Standard: IEC 60034-9 – Rotating electrical machines – Noise limits

#### #196: IEC 60034-14 (Functional)
The system shall comply/be evaluated against the Standard: IEC 60034-14 – Rotating electrical machines – Mechanical vibrations of certain machines with shaft heights 56 mm and higher – Measurements, evaluation and limits of vibration severity

#### #197: Practical rules for assessment of inverter-induced bearing currents in inverter fed AC motors (Functional)
The system shall comply/be evaluated against the Standard: Practical rules for assessment of inverter-induced bearing currents in inverter fed AC motors up to 500 kW, A. Muetze, A. Binder (2007)

#### #198: IEC 60034 -25 (Functional)
The system shall comply/be evaluated against the Standard: IEC 60034 -25 Rotating electrical machines - Part 25: AC electrical machines used in power drive systems - Application guide

#### #199: ISO 281_2007 (Functional)
The system shall comply/be evaluated against the Standard: ISO 281_2007 - Bearing Life Rating

#### #200: ISO 14179-1 & 2 (Functional)
The system shall comply/be evaluated against the Standard: ISO 14179-1 & 2 - Gear Efficiency

#### #201: Standard: ISO 1940 (Functional)
The system shall comply/be evaluated against the Standard: ISO 1940 balancing grades, ISO 1940

#### #202: SAE J2208 Park Pawl (Functional)
The system shall comply/be evaluated against the Standard: SAE J2208 Park Pawl

#### #203: FMVSS 114 Park Pawl (Functional)
The system shall comply/be evaluated against the Standard: FMVSS 114 Park Pawl

#### #204: SAE J3158 Electric Park Brake (Functional)
The system shall comply/be evaluated against the Standard: SAE J3158 Electric Park Brake

#### #205: ASTM B117 - Salt spray (Functional)
The system shall comply/be evaluated against the Standard: ASTM B117 - Salt spray

#### #206: ISO 16232 (Functional)
The system shall comply/be evaluated against the Standard: ISO 16232 -Road vehicles — Cleanliness of components of fluid circuits

#### #207: ISO 7010 (Functional)
The system shall comply/be evaluated against the Standard: ISO 7010 - Graphical symbols -- Safety colours and safety signs -- Registered safety signs

#### #208: REG 100 (Functional)
The system shall comply/be evaluated against the Standard: REG 100 - Uniform provisions concerning the approval of vehicles with regard to specific requirements for the electric power train

#### #209: DIN 5480 (Functional)
The system shall comply/be evaluated against the Standard: DIN 5480 - Involute splines based on reference diameters

#### #210: ANSI B92.1 (Functional)
The system shall comply/be evaluated against the Standard: ANSI B92.1 - Involute splines and inspection

#### #211: ANSI B92.2M (Functional)
The system shall comply/be evaluated against the Standard: ANSI B92.2M - Metric module involute splines

#### #212: UNI ISO 4156 (Functional)
The system shall comply/be evaluated against the Standard: UNI ISO 4156 - Straight-sided splines for cylindrical shafts with internal centering. Dimensions, tolerances and verification

#### #213: DIN 5482 (Functional)
The system shall comply/be evaluated against the Standard: DIN 5482 - Internal and External Involute Spline Profiles - Space Width and Tooth Thickness Measurement Using Bells Or Pins

#### #214: UNI 4386 (Functional)
The system shall comply/be evaluated against the Standard: UNI 4386 - Relief grooves

#### #215: UNI 9321 (Functional)
The system shall comply/be evaluated against the Standard: UNI 9321 - Centering holes

#### #216: ISO 3497 (Functional)
The system shall comply/be evaluated against the Standard: ISO 3497 - Standard test Method for Measurement of coating Thickness by X-Ray Spectrometry.

#### #217: ISO 10049 (Functional)
The system shall comply/be evaluated against the Standard: ISO 10049 - Aluminium alloy castings - Visual method for assessing the porosity

#### #218: ISO 9915 (Functional)
The system shall comply/be evaluated against the Standard: ISO 9915 - Aluminium alloy castings — Radiography testing

#### #219: ISO 7722 (Functional)
The system shall comply/be evaluated against the Standard: ISO 7722 - Aluminium alloy castings produced by gravity, sand, or chill casting, or by related processes — General conditions for inspection and delivery

#### #220: CIRSP 25 (Functional)
The system shall comply/be evaluated against the Standard: CIRSP 25 - for LV and HV Systems

#### #221: ISO 11452 (Functional)
The system shall comply/be evaluated against the Standard: ISO 11452 - 2/4/8/9 for LV and HV

#### #222: ISO 10605 (Functional)
The system shall comply/be evaluated against the Standard: ISO 10605: Road Vehicles - Test Methods for Electrical Disturbances from Electrostatic Discharge

#### #223: ISO 7637 (Functional)
The system shall comply/be evaluated against the Standard: ISO 7637 2/3/4/5: Road Vehicles - Electrical Disturbances from Conduction and Coupling

#### #224: LV 123 (Functional)
| The system shall comply/be evaluated against the Standard: LV 123 |
| --- |

### #225: Fool Proof (Poke Yoke) Design (Functional)

#### #226: USCAR standards (Functional)
System Electrical Connections should be in accordance with USCAR standards. All requirements from regulation should be broken down to details (Hand clearance, Fixing Force, Sealing Spec, Cycles of connection/disconnection, Thermal properties, Materials on the pins to avoid Fretting.
T4 Team and CC Team Agreement on 2018-11-21. USCAR and DIN standards for connectors are quite similar. CC team will design with USCAR requirements on the first prototype, and cross check for additional requirements from DIN before environmental validation. USCAR2-6 or demonstrate similar compliance Example document : http://www.te.com/commerce/DocumentDelivery/DDEController?Action=showdoc&DocId=Specification+Or+Standard%7F108-94334%7FA3%7Fpdf%7FEnglish%7FENG_SS_108-94334_A3.pdf%7F2177694-6

#### #228: DIN standards for Electrical Collections (Functional)
System Electrical Connections should be in accordance with DIN standards
T4 Team and CC Team Agreement on 2018-11-21
USCAR and DIN standards for connectors are quite similar. CC team will design with USCAR requirements on the first prototype, and cross check for additional requirements from DIN before environmental validation.

#### #229: 60V+ cables and connections (Functional)
Any Cable or Connector with more than 60V should be orange colour, according to the international norm.
T4 Team and CC Team Agreement on 2018-11-21 Review of the feature - Confirmation on Design

#### #230: mechanical connections inside the Drive Unit (Functional)
All the mechanical connections inside the Drive Unit should have Poka Yoke features to eliminate faulty installation.
T4 Team and CC Team in Agreement on 2018-11-21 Review of the feature - Confirmation on Design
(Final details should be reviewed after initial casing design TBD)

#### #231: mechanical connections outside the Drive Unit (Functional)
All the mechanical connections outside the Drive Unit should have Poka Yoke features to eliminate faulty installation.
T4 Team and CC Team in Agreement on 2018-11-21 Review of the feature - Confirmation on Design
(Final details should be reviewed after initial casing design TBD)

### #232: Crash Safety (Functional)

#### #233: impact volume (Functional)
System should be designed to stay within the impact volume. (crash simulation team consulting)
Model of the PT as system to be shared with the Crash Safety team (12/11/2019). Results to be reviewed upon Crash Safety Simulations are performed by the T4 team.

#### #234: Crash Safety Concept (Functional)
System should be designed to allow Safe behaviour of the vehicle under the specified Crash Simulation Scenarios.
Define Crash Safety Concept (TBD) Simulation Scenarios TBD from T4 Vehicle Engineering Team. Model of the PT as system to be shared with the Crash Safety team (12/11/2019). Results to be reviewed upon Crash Safety Simulations are performed by the T4 team.

#### #235: Simulation Model (Functional)
System should be designed to allow Safe behaviour of the vehicle under the specified Crash Simulation Scenarios.
Setup the Simulation Model (TBD) Simulation Scenarios TBD from T4 Vehicle Engineering Team. Model of the PT as system to be shared with the Crash Safety team (12/11/2019). Results to be reviewed upon Crash Safety Simulations are performed by the T4 team.

#### #236: Powertrain effects Analysis (Functional)
System should be designed to allow Safe behaviour of the vehicle under the specified Crash Simulation Scenarios.
Powertrain effects Analysis (TBD) Simulation Scenarios TBD from T4 Vehicle Engineering Team. Model of the PT as system to be shared with the Crash Safety team (12/11/2019). Results to be reviewed upon Crash Safety Simulations are performed by the T4 team.

#### #237: FMSVSS, and ECE 79 (Functional)
System should be designed/packaged in a way that in case of a crash is not dangerous for the occupants
Check FMSVSS, and ECE 79

#### #238: TCU Control reply into crash signal (Functional)
TBD with vehicle team (27/01/2020)
Check with Matt and Nikos

## #2: Cost and Price (Functional)

### #239: Cost (CapEx & OpEx) (Functional)

#### #240: Target Cost for piece Price (final system) (Functional)
Target Cost for piece Price (final system). Piece cost (R2.2+R2.3+R2.4)
( TR-02.1.2 + TR-02.1.3 + TR-02.1.4 + TR-02.1.5 + TR-02.1.6 + TR-02.1.7 ) + ( TR-02.1.8 + TR-02.1.9 ) + ( TR-02.1.10 + TR-02.1.11 ) + ( TR-02.1..12 + TR-02.1.13)
Whole vehicle Cost : 14000 Euros
Target for Powertrain Cost (all PT components excluding battery) : 2000 Euros (Input from Sergey M)
DU Target Price : 1300 Euros (TBD) (without ParkLock Mechanism)
Park lock mechanism target : 150 Euros
Inverter Components : 550 Euros (TBC)
Intermediate Shafts : 120 Euros (TBD - 27/01/2020)
2020-03-04_mech_Calc_Electric_Motor.xlsm
2020-03-04_Cost_Analysis_Motor.pdf
2020-03-04_eMotor_Calculation.xlsm

#### #241: Inverter Piece Cost (Functional)
Includes:
- Casing
- Power Electronics

#### #242: Motor Piece Cost (Functional)
Includes:
- Stator
- Rotor
- LV Ancillaries

#### #243: Gearbox Piece Cost (Functional)
Includes:
- Casing
- Gears
- Bearings
- Shift Mechanism
- Sensors

#### #244: Inverter Tooling Cost (Functional)
Involve Manuel Scerttri

#### #245: Motor Tooling Cost (Functional)
Involve Manuel Scerttri

#### #246: Gearbox Tooling Cost (Functional)
| Involve Manuel Scerttri |  |
| --- | --- |

#### #247: Inverter D&D inc Testing (Functional)

#### #248: Motor D&D inc Testing (Functional)

#### #249: Gearbox D&D inc Testing (Functional)

#### #250: Design/Prototyping Costs (Functional)
| Target Cost for Design and Development works: Design/Prototyping Costs TBD *********** T4 Team and CC Team not aligned - TBC - 12/11/2019 Design/Prototype cost first estimation : V1 : 10X piece price (6 pieces) : £ 90k V2 : 5x Piece Price (20 pieces) : £130k V3 : 2x Piece Price (50 pieces) : £130k |
| --- |

#### #251: Testing Costs (Functional)
Target Cost for Design and Development works
Testing Costs - Testing Plan to be developed. TBD
******* T4 Team and CC Team not aligned - TBC - 12/11/2019
Testing cost estimation :
V1 : In House
V2 : £3 million
V3 : £7 million

#### #252: Cost for Equipment (Functional)
TO BE AGREED WITH ARRIVAL ELEMENTS / Arrival CC Components to agree ? Involve Manuel Scettri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 12/11/2019

#### #253: Cost for Logistics (Functional)
Cost for Logistics - Strategy TBD
TO BE AGREED WITH ARRIVAL ELEMENTS / Arrival CC Components to agree ? Involve Manuel Scettri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 12/11/2019

#### #254: Cost for Part Procurement (Functional)
Cost for Part Procurement - Strategy TBD
TO BE AGREED WITH ARRIVAL ELEMENTS / Arrival CC Components to agree ?Involve Manuel Scettri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 12/11/2019

### #255: Volumes (Functional)

#### #256: Prototype Quantities (Functional)
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
#### #257: Production Quantities (Functional)
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
### #259: Supplier Selection (Functional)
System design should be able to be manufactured by multiple suppliers.
T4 Team and CC Team in Agreement on 2018-11-21

### #261: Logistics of Part Procurement (Functional)
System design should be able to be manufactured without proprietary technologies.
T4 Team and CC Team in Agreement on 2018-11-21

### #262: VFM (Functional)
System design should be able to be manufactured without proprietary technologies.
T4 Team and CC Team in Agreement on 2018-11-21

### #263: Should Cost (Functional)
System should be reviewed under a "should cost" process, to understand the pricing options and trade offs with the supplier.
T4 Team and CC Team in Agreement on 2018-11-21
Should be after V1 initial design - Q3 2019

### #264: Cost of Servicing (Functional)

#### #265: Inverter (Functional)
Cost of Servicing (Target): Inverter
T4 Team and CC Team in Agreement on 2018-11-21
Should be competitive for an EV vehicle.
Ideally unit should not be serviceable.
Assumption is that the whole unit will be replaced.

#### #266: Electric Motor (Functional)
Cost of Servicing (Target): Electric Motor
T4 Team and CC Team in Agreement on 2018-11-21
Should be competitive for an EV vehicle.
Ideally unit should not be serviceable.
Assumption is that the whole unit will be replaced.

#### #267: Gearbox (Functional)
Cost of Servicing (Target): Gearbox (i.e. oil change)
| T4 Team and CC Team in Agreement on 2018-11-21 Should be competitive for an EV vehicle. Ideally unit should not be serviceable. Assumption is that the seals and bearings could be serviced. |  |  |  |  |  |  |
| --- | --- | --- | --- | --- | --- | --- |

## #3: Performance (Functional)

### #268: Range/Efficiency (Functional)

#### #269: WLTP Range (Functional)
Target to be set as energy consumption over cycle vs Battery SOC

#### #270: EPA Range (Functional)
Target to be set as energy consumption over cycle vs Battery SOC

#### #271: Real world Efficiency (Functional)
Real world Efficiency : 200km (@50% load) +/-10% of Brochure Figure
See Durability Requirements (R6.1)
( 2018-11-13 )
|  | T4 Team and CC Team not in agreement on 2018-11-21. Further work required from Systems team to breakdown the targets for efficiency to components. |  |
| --- | --- | --- |

#### #272: energy consumption (Functional)
The energy consumption of the unit should be limited to XXX percentage/kwh per operation. TBD
( 2018-11-13 )
T4 Team and CC Team not in agreement on 2018-11-21. Further work required from Systems team to breakdown the targets for efficiency to components.

### #273: Performance (Functional)

#### #274: Vehicle Parameters (Functional)
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
#### #275: Maximum Peak (30 sec ) Torque/Power Vehicle Traction (Functional)
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
#### #276: Maximum Continuous Torque/Power Vehicle Traction (Functional)
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
### #278: Smooth Control Dynamics (Functional)

#### #279: Propulsion System SysRS (Functional)
T4 and CC team not in Agreement on the power curves for Peak and Continuous not OK TBD
Check Document for Features request

#### #280: Maximum Interruption Time (Functional)
TCU Gear Shift - Maximum Interruption Time
TCU will complete all standard gearshifts within the target time.
This is the maximum time that wheel torque can be interrupted for ratio change; from the point of hand over of torque control from DTU to TCU, to the point at which TCU hands torque control back to the DTU

#### #281: Shift shock (Functional)
TCU Gear Shift - Shift shock
Maximum acceptable shift shock during a standard ratio change.
Shift shock to be measured by seat rail accelerometer and calculated as outlined here.
(Research on Gear Shifting Process without Disengaging Clutch for a Parallel Hybrid Electric Vehicle Equipped with AMT. Hui-Long Yu, Jun-Qiang Xi ,Feng-qi Zhang, and Yu-hui Hu.)

#### #282: TCU Hardware Protection (Functional)
Temperature:
Above specified overheat temperature higher gear selection will be prioritised by TCU.
Above specified de-rate temperature, torque should be limited. (TBC on torque limit; step reduction, ramping profile, etc.)
Over-speed:
TCU shall avoid over speed conditions via torque demand control. TBC
Power:
TCU shall avoid exceeding power handling capability via torque demand control. TBC

### #283: Park Lock Functionality (Functional)

#### #284: System should have the ability to keep the vehicle parked when commanded. (Functional)

#### #285: System Should be part of the Total Vehicle Control Architecture shown below (Functional)
Architecture Design preliminary investigations. Control Logic Expected to be in place 14/02/2019.
Current Assumption
Vehicle main controller will request torque at the wheels, Powertrain DU controller will decide gear and control the gear shift.
Vehicle main controller will get Power limits (or torque) from BMS and PT / Inverter and make the arbitration.
PT DU Controller Slave unit to Vehicle Main Controller.
Check with Yuri Laymin TBD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

## #4: Accesibilty (Functional)

### #286: Limited Access (Functional)
The system should provide protection against access to PT components.
The system should be protected and sealed for life.
T4 team and CC- Team not in Agreement
Preliminary sensitivity analysis to be done by drive unit team - discussion with Patrick needed (27/01/2020)

### #287: Software Security (Functional)
The system software should have a secure architecture so no unauthorised person can change or affect PT calibrations. Details TBD with StP team.
T4 team and CC- Team in Agreement

### #288: Access to Critical Components (Functional)
The system should have sufficient protection in the case of an accident, so no danger is present to the support agencies (e.g fireman or ambulance)
T4 team and CC- Team in Agreement

## #5: Modularity Between Projects (Functional)

### #289: Re-use of Components Between Projects (Functional)
System should have components that are common between projects.
Current motor assumption - Motor V3.05 - active parts shared between B12 and T4
Change of motor assumption to be done with approval from B12 team

### #290: Flexibility Between Configurations (Functional)
System should have components that can be used in conjunction with other components.

## #6: Robustness (Quality) (Functional)

### #291: Reliability (Functional)

#### #292: System Should be reliable to the designated environment. (Functional)
- Target for Millage : 480,000 km (300,000 miles)
- Design lifetime of the vehicle: 15 years
- Target for degradation of the main functions at the end of the life: All attributes 80% accepted
- Target for infant Mortality Allowance: TBD
- System should incorporate (where possible) functions to allow improvement of operations and removal of noise factors (e.g warm up of oil to evaporate water content)

#### #293: The Durability and Reliability Strategy for all Arrival Projects consists of multiple separate work packages. (Functional)
Phase A - Driving Cycles - External Factors
A1.0) Collect the necessary data from the customers.
A2.1) Establish realistic driving cycles for the use case (Speed/Time).
A2.2) Establish realistic gradient gradient cycles for the use case (Gradient/Time).
A2.3) Establish realistic Loading/Unloading Scenarios for the use Case.
A2.4) Extreme Case Scenarios.
A3.1) Create the input for the simulations.
A3.2) Agree and align the regenerative braking component, based on vehicle level torque blending strategy.
Phase B - Simulink 0D simulation Studies
1) Create Vehicle Representative Model.
2) Define the Powertrain Architecture.
3) Create simulation Matrix based on Assumptions of Use Case.
4) Generate Histograms with Damage Excitation Mechanisms vs Required Durability targets. Different failure mechanisms need to use different histograms.
5) Issue report and share data with the engineering team for detailed evaluation of design.
Phase C & D - Romax/Ansys/MotorCAD Component Durability Evaluation
1) Evaluate Loads based on current design.
2) Update design as needed to meet safety factors.
Phase E - Testing and Validation
1) Generate test conditions for durability evaluation. Evaluate Loads and Hours of testing.
2) Perform the validation testing.
3) Issue Report with Validation Testing Results (8D if failure, Sign off report if success).
Phase F - Sign off
Generate the model of performance degradation for use in the predictive maintenance algorithm.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

#### #294: external factors (Functional)
Phase A
the external factors that should be considered during the development process of the powertrain system of the vehicle:
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Report: Driving Cycle of a Commercial Vehicle
V2GO data set
Customers - Contact Details
Requirements
Driving Style/Conditions: the data for this category are produced by converting the speed of the vehicle into a graphical representation vs time. These data is to be collected from a GPS device during the daily driving cycle of the vehicle.
Road Profile: the daily gradient distribution data contains the elevation profile of the road during the cycle. The percentage of the slope between two consecutive GPS positions can be calculated using the longitude, the latitude and the altitude.
Payload distribution: the payload distribution is a parameter that changes from customer to customer. The data collection for this category is time consuming and it can have a big deviation from reality because of the lack of information during the loading and the unloading processes.
Simulations (losses) - T4 v1
Data Management
The data from every driving cycle must be modified in order to create the final information that can be used for the simulations. For this purpose, an excel sheet is used. The longitude and the latitude are used as an input to a GPS signal converter:
http://www.gpsvisualizer.com/elevation
This converter produces the altitude data. Then the excel sheet uses 2 specific equations to calculate the distance between two consecutive points of the route. At the final stage the gradient is calculated as a percentage using the previous mentioned data.
Assumptions
1) Road Profile:
- the elevation profile for every driving cycle is a unique and realistic scenario but it is limited by the geomorphological features (elevation, slope) of the area that the samples were taken from.
2) Driving Style/Conditions:
- the sample of the daily driving cycles includes the information about how the driver behaves (acceleration and deceleration style).
- the driving cycle can inform about the type of the road (inner city, suburban or motorway) and the traffic conditions (rush hour or no-rush hour).
- a large sample of speed vs time driving cycles represents an accurate enough set of realistic scenarios. For this reason there is no need to create custom ones.
3) Payload:
- every customer uses the payload of the vehicle in a different way. A sample of different custom loading and unloading conditions will be assumed.
4) Data logging inaccuracies:
- the customers are using different data logging devices. Every device may use different logging frequency. (Warburton's GPS devices capture data every minute, devices that are used in V2GO project capture 10 positions per minute).
- the accuracy of the GPS signal can be affected by various parameters. In case that some values are missing, an assumption will be made.

#### #295: Slow Urban (Functional)
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
#### #296: Free Flow Urban (Functional)
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
#### #297: Delivery Cycle (Functional)
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
#### #298: Rural Total (Functional)
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
#### #299: Motorway Total (Functional)
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
#### #300: Load Conditions - Payload (Functional)
https://docs.google.com/spreadsheets/d/1ks5FslokTzRwdw5-OxFWNVff1ffjUrw10ECPeRurVLA/edit#gid=0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

#### #301: Durability Extreme Events (Functional)
Extreme Grades against Drive cycles
Given slope histogram in the UK assume 1% of kilometers to be done @ the highest possible speed allowed in the slope.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

#### #302: Slope Conditions (Functional)
(based on customers)
Sainsbury's : 10% (steepest slope/ramp)

#### #303: Torque Braking Blending Strategy (Functional)
Torque Braking Blending Strategy from T4 Vehicle Dynamics.
The system should be designed with a regenerative torque profile according to the following assumption.
1) DU Limits for Regen continuously to be shared with T4 team as a graph
3) ABS integration with the ABS system. Should be designed in a way to zero the torque when ABS is activated. DU team awaiting for specs (27/01/2020)
Agreement Not reached TBD in Mid February

#### #304: Extreme Events Driveline Calculation. (Functional)
Driveline Shocks Calculation (TBD - 27/01/2020) Robin Langhorn Target date 2wks
- Check with Ahmed on mounting points
- Check on gears
1.20 Chassis Structure Attributes Requierments
https://wiki.arrival.com/display/T4/Structural+Performance

#### #305: Simulations Matrix (Functional)
https://docs.google.com/spreadsheets/d/1QPOoPQy3tcveETmRhoMqfxGiN5TIBQwAk-3zoD_yF0E/edit#gid=0

#### #306: Speed histograms for fleet average (5 or 10kph bins) (Functional)

#### #307: Slopes histograms for fleet average (if available) (Functional)

#### #308: Loading of the vehicles (ideally if measured in kilos per shipment) (Functional)

#### #309: Temperatures and hours of operation (Functional)

#### #310: Temperature Sensor Redundancy (Functional)
System shall have 2 Temperature sensors on the motors, to provide redundancy on the operations (Details to the Sensor System Requriements()
Currently Inverter assumption is with one sensor reading circuitry for Inverter.
Requirement to add an additional temperature sensor system is shared with inverter team, implementation in future releases shall be notified back to Drive unit team.
Design will include it, and Drive Unit is future proof.

#### #311: Customer Information & External Collaborations (Functional)
https://wiki.arrival.com/pages/viewpage.action?pageId=95026853

### #312: Durability (Functional)

#### #313: Vehicle Should be robust in seeling locations (Functional)
The system should be robust in the following environments :
Countries that the vehicle will be sold (Get histograms for temperatures/humidity/altitudes). Combined Temperature/Humidity Histograms for whole markets. Grouping of histograms to generic categories is allowed (e.g Northern, Southern, Asia-Pacific etc) .
Robustness Definition : The execution of the specified function to the specified level of performance in the presence of Noise. 5 Noise Factor Framework (Next pages more details)
Partially Defined TBD

#### #314: Salt Spray (Functional)
The system should be robust in the following environments : Salt Spray profiles Sand, dust, stone chipping and dirt/mud. Salt spray 300h TBD later stage

#### #315: Vibration profiles (Functional)
The system should be robust in the following environments : Vibration profiles based on driving/road conditions to the specified countries TBD

## #7: Comfort Quality (Functional)

## #8: Service Operations (Functional)

## #9: Documentation (Functional)

## #10: Integration (Functional)

## #11: Manurfacturing (Functional)

## #12: Simplicity (Functional)

## #13: Sensors and Connectivity (Functional)

## #14: Competitior Benchmarking (Functional)

## #15: Vertical Assembily (Functional)

## #16: Legal (Functional)

## #17: End of Life (Functional)

## #18: Operations (Functional)

## #25: Motor Requirements (Functional)

## #26: DriveUnitUpdates (Functional)

### #27: Stator Core Update (Functional)
Manual
Prepare serial log books for assemblies and inspection.
1) Serial Number of units etched in the Stack
2) Barcode or QR code for internal serial numbers on the stack
3) Marking Slot Numbering with design to indicate the slot numbers
4) Modify the design to be Poka-Yoke on up-down sides.
5) Need Jig for inspection. The current stand is not stable and damages laminations
6) Better tolerance requirements on the stator are required
Automated
1) Barcode or QR code for internal serial numbers on the stack
2) Visual Inspection System ??
Detail
Review the fabrication of the stator, optimisation opportunies on the design

### #28: Edgewise Coil Update (Functional)
Manual
Phase U coils to arrive from supplier already trimmed to the correct length and with the enamel stripped. But it will increase BOM
Automated
1) Phase U coils to arrive from supplier already trimmed to the correct length and with the enamel stripped.
2) Pre-foil coil ends to allow System 1.3 automated insertion

### #29: Slott Liner Creasig and folding (Functional)
Supplier to deliver perform quality check on slot liner folding side and total length. Ask them to get a creasing machine.
** If rolled up lamination is used - check insulation concept
1) Supplier to deliver perform quality check on slot liner folding side and total length. Ask them to get a creasing machine.
2) Detailed Specification Procedure to be send to the supplier

### #30: slott liner wrapping around coil (Functional)
1) Wrap kapton tape as close as possible to the endwinding to prevent nomex paper from tearing at the creases.
2) Cuffing the nomex paper before the insertion
3) Many of the end caps required re-work. Some of them would fit a slot of the stator and the same one would not fit another slot on the same stator
** If rolled up lamination is used - check insulation concept
automated
1) Supplier to deliver perform quality check on capton tape. 2) Detailed Specification Procedure to be send to the supplier
3) Slot liner manufacturing procedure to be requested from the supplier (data required)

### #31: End Caps Placing in coil (Functional)
1) Check tolerance stackup of the stator/end caps
2) Clipping Feature on the End Cap, to lock in place inside the coil
3) Include PT100 features slot, to incoroporate the sensor withing the end cap.
4) Need way to insert the coils perpendicularly to the slots
automated
1) Holding points in the inside of the end cap that will allow robotic assembly / pickup

### #32: coil insertion (Functional)
1) Wedges on X1 build were not perfect, and needed to be trimmed. Check that the wedges are manufactured correctly, and strict the control for MSA
2) Roll up lamination design Study
3) Segmented tooth design investigation Study
automated
1) Segmented Tooth Design Investigation
2) Rollup lamination Design Investigation

### #33: Hipot check (Functional)
Design Custom Connector that will directly couple to our system into a belt system (spring loaded or similar)
Lock in place and perform the test automatically

### #34: Cooling Liner Insertion (Functional)
1) Cooling liners to be fitted after the coils
2) More design studies required
3) Design Feature on coolant liner to stay at the correct hight
4)The liners would not wedge consistently leaving different gaps betweein the liner and the outer case
5) Many leaks from the spigot to the main body conection even when checked -> Abuse triggered failure mode
6) High Rejection ration of the coolant liner
7) Amount of sealant is uncontrolled
8) Gluing the coolant liners to support until potting resulted in scrapping coils when rework was required.

### #35: Cooling manifold insertion (Functional)
Cooling Manifold study needs to be performed (again)
When inserting the hose it is difficult to estimate how far the hose needs to go on the spigot
We are using a set length of hose but deviations on coils and stator result in deviations on this process. Need a tool to meadure and compensate or more preferrably standardise
Hose selection needs to be reviewed. Testing at 3bars abuses the hoses by expansion.
Y-splitter manufacturing deviations resulting in clashes with the hole in the case.
Y-splitter is not aligned to the coolant liner spigots resulting ins sharp angles
Y-splitter height and position resulted in classes with the lid of the case. Had to cut length in order to close the lig of the motor. Had to trim 1mm from the two hosetails and 3mm from the treaded fiting.
Nuts of the y-spliter had to be cut to 9mm (@manos to confirm)
Y-splitter hole is not sealed (We use an o-ring)
Sealant sometimes blocks the coolant liner hole

### #36: slott wedges insertion (Functional)
1) Design improvement opportunity, add a t-head feature at the end of the wedge for locking.
2) Lat batch for the v3.05 stator was off spec for all of them !!!!

### #37: Weld Star Points (Functional)
Starpoints' insulation can be higher so that the coil output does not need to be bent so short
Uncotrolled Temperature, Duration of expore to heat, amount of soldering and requires two people.
Need a way to support the part during soldering and pressung the coil end down

### #38: Weld phase connection (Functional)
Starpoints' insulation can be higher so that the coil output does not need to be bent so short
Uncotrolled Temperature, Duration of expore to heat, amount of soldering and requires two people.
Need a way to support the part during soldering and pressung the coil end down

### #39: pt100 placement (Functional)
1) PT100 sensor placement is very fragile, needs to be improved within the design with the wiring
2) Make a hole on the side of the End cap - and a groove, to allow the sensor to be placed perpendicular to the coil
3) Method to identify which sensor is which after installation and potting

### #40: Pressure test cooling (Functional)
1) Vacuum Test Investiation
2) Attachment Jig for easy Testing setup
3)Pressure test in liners and hoses must be done again after the final assembly of the housing and lid
4) The hoses that connect to spiggot should be longer before the test and trimmed to the final dimenssion afterwards in order not to be damaged from the clips during testing

### #41: Install bearing into housing (Functional)
Needs to happen after potting, to ensure no resudue contaminates the bearing

### #42: Insert Stator Assembly into Housing (Functional)
One of the case was required to be heated (S/N: 002)
Loose fit of the case and smaller bolts resulted in misaligned holes for (Stator vs case) (S/N:003)
Case or stator need a feature to create the correct amout of gap to the case face (29mm) Also the feature could poka-yoke the correct rotational direction of the stator (so the HV rings fit without issues)

### #43: Potting of Stator (Functional)
1) Investigate options for Rollup lamination design and potting
Another challenge Thor did not expect was the inlet/outlet of the cooling system to be as it is. With the present tooling, it is not possible to keep the inside of the cooling system at the same pressure. This will mean that the hose will tend to expand a bit less than 1 bar when vacuum is applied to the stator.
- Instead of the EP2000 resin we were planning to use, Thor suggested using the same one they are applying for CRA, which is C(a)-1123A+PDR-2205-1 from Von Roll (spec sheet attached). It is 1.2-1.3 W/Km instead of 1.7-1.9 W/Km but the procedure is much simpler as it does not require pre-heating the resin nor pre-gelling. The results of this resin are physically good , thermally is not as good as EP2000 but that is for a properly prepared EP2000 and the machines that Huebers utilizes.
- If we had forced them to go with EP2000, they could do it but the risk is bigger, as nor do they have proper tooling to do it neither the experience with the resin. In any case, 1.2-1.3 W/Km is much higher than 0.35 W/Km from simple impregnation.
SIPOC needs to be updated: Fit all screws to the correct length before sending for potting to avoid blockage of the hole

### #44: Insert Magnets (Functional)
Magnets could have the north dot covering part of the edge so that one can tell if the position of the magnets is right by looking a finished stack instead of only relying on the compass.
Design jig to keep magnets aligned axially and for drying/curing. Minimise contact area. Example solution, PTFE jig (non-sticky material) with bumpy surface (minimal but regular contact). Material separating the magnets in shipping (likely PTFE) worked well for non-stick.
Vladimir has implemented a new method by pre-curing the glue

### #45: Assemble Rotor (Functional)
Keyway and Sub-Assembly Design to be reworked
Stack assembly with non magnetized pucks.
Review outside pattern as it is not unique, currently possible to have a magnetically correct rotor with non-unique pattern on the outside.
REVIEW RESIN RETENTION METHOD! Change to a mechanical method?
Modify the endplates to have 2 keys, polar opposite to each other, ensuring more robust inherrent balance (remove user error risk)
When using the c-spanner there is not controlled torquing od the nut and there is no way of compressing the stacks in place

### #46: Balance Rotor (Functional)
Investigate with solid benchmarking data the size of the balancing plate, the material and the systematic imbalance we are expected to have. More details see study from @nikolay
Remove stickers and clean excess residue rom the surface of the rotor before sending for balancing

### #47: Fit Bearing to Rotor (Functional)
Check bearing specification

### #48: Install Rotor Assembly into Housing (Functional)
Update the SIPOC with the following improvement: Fit the Lid along with the rotor and the wave washer on hte tooling and fit them all in one go to the stator because it helps with the alignement of the rotor during insertion

### #49: Fit Front cover (Functional)
Housing Review is required, to allow proper recalculation of the fits and tolerances. Bearings reviews are required
This Process step could be integrated with the Rotor Insertion Process Step. To be further analysed with the tool design team (Greg)
SIPOC needs to be updated with the wave washer insertion

### #50: Fix Front cover (Functional)
Need to add torque specs for lid bolts

### #51: Fit stator Grub Screws (Functional)
Spacers need to have a termination feature at the correct height. Also need to identify if there is a requirement for threadlock (at the moment we are using but not on the sipoc)

### #52: Press fit Resolver Rotor to Motor Shaft (Functional)
Needs review, resolvers falling to bits during asembly

### #53: Assemble LV Connector to Housing (Functional)
add feature of servce loop
No guidlines on what to do with the extra PT-100

### #54: Assemble HV Connector (Functional)
Difficult to cut the insulation and shield to length. Need something to allow cuts at the correct length
Custom-made die for the shield crimping proved difficult to use with the crimping tool.
We need a crimping tool !!!
Need a way to mark pahses

### #55: Assemble sea to housing (Functional)
oring is to big for HTE motor

### #56: Fit Motor connector cover to housing (Functional)
Need Banana plugs for instrumented motors to measure phase voltage and IR sensor

### #57: Replace Slott with Hex (Functional)
Update Grub Screw slott with a Hex
